module ios-essential {

    yang-version 1;
    namespace "urn:opendaylight:params:xml:ns:yang:ios:essential";
    prefix "cli-ios-e";

    revision "2017-05-20" {
        description "Initial revision";
    }

    container vrfs {
        list vrf {
            key "id";

            leaf id {
                type string;
            }

            leaf description {
                type string;
            }
        }
    }

    container interfaces {
        list interface {
            key "id";

            leaf id {
                type string;
            }

            leaf admin-status {
                type boolean;
            }

            leaf protocol-status {
                type boolean;
            }
        }
    }

    /*
    VERSION:
    OS_FAMILY: IOS-XE
    PLATFORM: CSR1000v
    OS_VERSION: 03.16.05.S - Extended Support Release
    SYS_IMAGE: bootflash:packages.conf
    SERIAL_ID: 9QWUHXQ2ROK
    CONF_REG: 0x2102
    SYS_MEMORY: 3988292 KBytes
    HW_ENV: VIR
    */
    container version {
        config false;

        leaf os-family {
            type string;
        }

        leaf platform {
            type string;
        }

        leaf os-version {
            type string;
        }

        leaf sys-image {
            type string;
        }

        leaf serial-id {
            type string;
        }

        leaf conf-reg {
            type string;
        }

        leaf sys-memory {
            type string;
        }

        leaf hw-env {
            type string;
        }
    }

}
